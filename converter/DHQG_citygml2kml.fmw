FME workspace DHQG_citygml2kml.fmw

Parameters:
- DestDataset_OGCKML = ../data/DHQG_Test.kml   # Destination Google KML File
- SourceDataset_CITYGML = ../data/DHQG.gml   # Source CityGML File(s)

Readers:
- CITYGML_1: CITYGML from $(SourceDataset_CITYGML)

Writers:
- OGCKML_1: OGCKML to $(DestDataset_OGCKML)

FloorSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> Deaggregator
Road (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
    -> Deaggregator
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> Deaggregator
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> Deaggregator
Deaggregator
    EXPLODE_INSTANCES = No
    LIST_ATTR_MODE_LOOKUP = LEAN
    GEOM_NAME_FIELD = _geometry_name
    PART_NUMBER_FIELD = _part_number
    MODE = Flatten One Level
    SPLIT_COMPOSITES = No
    DEAGGREGATED -> Triangulator
Triangulator
    TIN_SURFACE -> MeshMerger
MeshMerger
    ACCUM_INPUT_ATTRS = Get Attributes From One Representative Feature
    MESH -> CsmapReprojector
CsmapReprojector
    INTERPOLATION_TYPE_NAME = Nearest Neighbor
    VERTICAL_HANDLING = Ignore heights and leave them unchanged
    RASTER_CELL_SIZE = Preserve Cells
    DEST = LL-WGS84
    REPROJECTED -> DHQG_Test (writer OGCKML_1)
DHQG_Test (writer OGCKML_1)
    attributes: gml_id kml_char(255), gml_parent_id kml_char(255), citygml_target_uri kml_char(255), citygml_feature_role kml_char(255), citygml_feature_role_attr_name kml_char(255), citygml_feature_role_attr_val kml_char(255), gml_description kml_char(255), gml_name kml_char(255), citygml_creationDate kml_char(255), citygml_terminationDate kml_char(255), externalReference{}.externalObject.name kml_char(255), externalReference{}.externalObject.uri kml_char(255), externalReference{}.informationSystem kml_char(255), citygml_generalizes_to{}.xlink_href kml_char(255), citygml_relative_to_terrain kml_char(33), citygml_relative_to_water kml_char(38), citygml_appearance{}.xlink_href kml_char(255), citygml_level_of_detail{} kml_char(255), citygml_opening{}.xlink_href kml_char(255), citygml_class kml_char(255), citygml_class_codeSpace kml_char(255), citygml_function{} kml_char(255), citygml_function{}.codeSpace kml_char(255), citygml_usage{} kml_char(255), citygml_usage{}.codeSpace kml_char(255), citygml_traffic_area{}.xlink_href kml_char(255), citygml_auxiliary_traffic_area{}.xlink_href kml_char(255), _geometry_name kml_char(200), _part_number kml_char(200)
