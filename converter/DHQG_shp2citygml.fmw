FME workspace DHQG_shp2citygml.fmw

Parameters:
- SourceDataset_ESRISHAPE = /home/canh/UET3D/data/DHQG.shp   # Source Esri Shapefile(s)
- DestDataset_CITYGML = /home/canh/UET3D/data/DHQG.gml   # Destination CityGML Document
- SourceDataset_ESRISHAPE_3 = $(FME_HOME)xml\CityGML\writer_feature_types\CityGML_feature_types.xml   # Source Esri Shapefile(s)
- SourceDataset_JPEG = /home/canh/UET3D/data/textures/*.jpg   # Source JPEG File(s)

Readers:
- ESRISHAPE_1: ESRISHAPE from $(SourceDataset_ESRISHAPE)
- ESRISHAPE_2: ESRISHAPE from $(SourceDataset_ESRISHAPE_3)
- JPEG_1: JPEG from $(SourceDataset_JPEG)

Writers:
- CITYGML_1: CITYGML to $(DestDataset_CITYGML)

Bookmark: Input
DHQG (reader ESRISHAPE_1)
    attributes: Id short, height short, name char(16)
    -> RoadSearcher

Bookmark: Preparation
RoadSearcher: StringSearcher
    STRING_TO_SEARCH = @Value(name)
    REGEXP = Road
    CASE = no
    MATCHED -> RoadAttributeCreator
    NOT_MATCHED -> UUIDGenerator
UUIDGenerator
    UUID_ATTR = _uuid
    -> StringConcatenator
StringConcatenator
    ACTION = Overwrite Existing Attributes
    PARM_LINE = ID@Value(_uuid)
    ATTRLIST = _uuid
    -> StringReplacer
StringReplacer
    SRC_ATTRS = name
    REPLACE_TEXT = _
    FIND_TEXT = " "
    NO_MATCH = _FME_NO_OP_
    REGEXP = YES
    CASE = NO
    -> SurfaceAttributeCreator
    -> BuildingAttributeCreator

Bookmark: Create GML Attributes
RoadAttributeCreator: AttributeCreator
    ATTR_TABLE:
      SET_TO citygml_lod_name = lod2MultiSurface
      SET_TO citygml_feature_role = cityObjectMember
    -> RoadGeometryPropertySetter
BuildingAttributeCreator: AttributeCreator
    ATTR_TABLE:
      SET_TO citygml_lod_name = lod1MultiSurface
      SET_TO citygml_feature_role = cityObjectMember
      SET_TO gml_id = @Value(_uuid)
      SET_TO gml_name = @Value(name)
    -> Building (writer CITYGML_1)
SurfaceAttributeCreator: AttributeCreator
    ATTR_TABLE:
      SET_TO citygml_lod_name = lod2MultiSurface
      SET_TO citygml_feature_role = boundedBy
      SET_TO gml_parent_id = @Value(_uuid)
    -> Roof3DForcer
    -> Floor3DForcer
    -> Chopper

Bookmark: Road
RoadGeometryPropertySetter: GeometryPropertySetter
    SRC_ATTRS = citygml_lod_name
    REMOVE_ATTRIBUTE = No
    SETTYPE_PARAM = Traits From Attributes
    OVERWRITE_CHOICE = Yes
    SET -> Road (writer CITYGML_1)
Road (writer CITYGML_1)
    attributes: citygml_feature_role xml_char(200)

Bookmark: Building
Building (writer CITYGML_1)
    attributes: citygml_feature_role xml_char(200)

Bookmark: Roof
Roof3DForcer: 3DForcer
    KEEPZVAL = No
    ZVALATTR = @Value(height)
    -> RoofGeometryPropertySetter
RoofGeometryPropertySetter: GeometryPropertySetter
    SRC_ATTRS = citygml_lod_name
    REMOVE_ATTRIBUTE = No
    SETTYPE_PARAM = Traits From Attributes
    OVERWRITE_CHOICE = Yes
    SET -> RoofSurface (writer CITYGML_1)
RoofSurface (writer CITYGML_1)
    attributes: citygml_feature_role xml_char(200)

Bookmark: Floor
Floor3DForcer: 3DForcer
    KEEPZVAL = No
    ZVALATTR = 0
    -> FloorGeometryPropertySetter
FloorGeometryPropertySetter: GeometryPropertySetter
    SRC_ATTRS = citygml_lod_name
    REMOVE_ATTRIBUTE = No
    SETTYPE_PARAM = Traits From Attributes
    OVERWRITE_CHOICE = Yes
    SET -> FloorSurface (writer CITYGML_1)
FloorSurface (writer CITYGML_1)
    attributes: citygml_feature_role xml_char(200)

Bookmark: Create Wall ID
Chopper
    MAX_VERTICES = 2
    REMNANT_ATTR = _remnant
    CHOPPED_ATTR = _chopper
    MODE = By Vertex
    -> Counter
Counter
    DOMAIN = @Value(name)
    SCOPE = Global
    START = 1
    CNT_ATTR = _count
    -> WallIDAttributeCreator
WallIDAttributeCreator: AttributeCreator
    ATTR_TABLE = SET_TO gml_id = WALL_@Value(name)_@Value(_count)
    -> Extruder

Bookmark: Set Geometry
Extruder
    DISTANCE = @Value(height)
    DIRECTION = Vertical
    -> WallGeometryPropertySetter
WallGeometryPropertySetter: GeometryPropertySetter
    SRC_ATTRS = citygml_lod_name
    REMOVE_ATTRIBUTE = No
    SETTYPE_PARAM = Traits From Attributes
    OVERWRITE_CHOICE = Yes
    SET -> AttributeCreator_2

Bookmark: Add Appearance
AttributeCreator_2
    ATTR_TABLE = SET_TO _tmp = @Value(gml_id)
    -> AppearanceSetter [GEOMETRY]
JPEG (reader JPEG_1)
    -> AttributeCreator
AttributeCreator
    ATTR_TABLE = SET_TO _tmp = @Value(fme_basename)
    -> AppearanceSetter [APPEARANCE]
AppearanceSetter
    GQUERY:
      for $geom in //geometry
      where $geom/count(parent::geometry) = 0
      return number($geom/@fme_id)
    TEXTURE_V_OFFSET2 = 0.0
    TEXTURE_MAPPING_TYPE_CHOICE = Surface Normal
    TEXTURE_V_SCALE_FACTOR = 1.0
    SET_ON_SIDE = Front and Back Sides
    USE_EXISTING_TEXTURE_COORDINATES = No
    TEXTURE_U_SCALE_FACTOR = 1.0
    GROUP_BY = _tmp
    TEXTURE_U_OFFSET2 = 0.0
    DEF_STORAGE = Create New Definitions
    -> WallSurface (writer CITYGML_1)
WallSurface (writer CITYGML_1)
    attributes: citygml_feature_role xml_char(200)
